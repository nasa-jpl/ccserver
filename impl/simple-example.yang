module simple-example {
  yang-version 1.1;
  namespace "urn:example:simple";
  prefix ex;

  revision 2026-06-04 {
    description "Initial revision.";
  }

  container data-store {
    list item-list {
      key "index";

      leaf index {
        type uint32;
      }

      leaf value {
        type int32;
      }

      list sub-item-list {
        key "index";

        leaf index {
          type uint32;
        }

        leaf sub-value {
          type int32;
        }
      }
    }

    leaf data-store-value {
      type uint32;
    }
   }
}
